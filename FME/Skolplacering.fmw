FME workspace Skolplacering.fmw

Parameters:
- key =   # Graphhopper api key
- api_graphhopper_url = http://localhost:8989   # Path to graphhoper api
- CachedElev = Nej   # Använd cachade elever
- CachedSkolor = Nej   # Använd cachade skolor
- DestDataset_XLSXW = $(FME_MF_DIR_USERTYPED)Resultat\avstandtillskola.xlsx   # Destination Microsoft Excel File
- DestDataset_XLSXW_3 = $(FME_MF_DIR)Resultat\avstandtillskolameta.xlsx   # Destination Microsoft Excel File
- graphhopperCacheFileName = calls@Timestamp(^Y^m^d^H^M).json   # Graph hopper cache file name

Writers:
- XLSXW_1: XLSXW to $(DestDataset_XLSXW)
- XLSXW_2: XLSXW to $(DestDataset_XLSXW_3)

Creator_3
    GEOMTYPE = Geometry Object
    NUM = 1
    CREATED -> Skolor
    CREATED -> Elever
    CREATED -> Skolor_eller_elever
Skolor: Tester
    BOOL_OP = OR
    TEST_DESCRIPTION = ""
    TEST_CLAUSE = TEST $(CachedSkolor) = Ja
    TEST_MODE = Automatic
    PASSED -> FeatureReader_3 [INITIATOR]
Note: Läs Readme.md
FeatureReader_3
    DATASET = $(FME_MF_DIR_ENCODED)Indata\Skolor.geojson
    ATTR_ACCUM_MODE = Only Use Result
    GEOJSON_USE_SEARCH_ENVELOPE = NO
    GEOJSON_CLIP_TO_ENVELOPE = NO
    GEOJSON_FLATTEN_MODE = ALL_LEVELS
    FORMAT = GEOJSON
    GEOJSON_USE_BASENAME_AS_DEFAULT_FEATURE_TYPE = Yes
    INTERACT = <No Spatial Filter>
    OUTPUT_FEATURES_DISPLAY = Schema and Data Features
    COMBINE_GEOM = Use Result
    ATTRIBUTES = output,"S.Adress,S.Skola,S.mergeAdress,S.long,S.lat,fme_geometry{0}"
    -> FULL_JOIN [Skolor]
Elever: Tester
    BOOL_OP = OR
    TEST_DESCRIPTION = ""
    TEST_CLAUSE = TEST $(CachedElev) = Ja
    TEST_MODE = Automatic
    PASSED -> FeatureReader_2 [INITIATOR]
FeatureReader_2
    DATASET = $(FME_MF_DIR_ENCODED)Indata\elever.geojson
    ATTR_ACCUM_MODE = Only Use Result
    GEOJSON_USE_SEARCH_ENVELOPE = NO
    GEOJSON_CLIP_TO_ENVELOPE = NO
    FORMAT = GEOJSON
    GEOJSON_FLATTEN_MODE = ALL_LEVELS
    GEOJSON_USE_BASENAME_AS_DEFAULT_FEATURE_TYPE = Yes
    INTERACT = <No Spatial Filter>
    OUTPUT_FEATURES_DISPLAY = Schema and Data Features
    COMBINE_GEOM = Use Result
    ATTRIBUTES = Output,"UniqValue,E.Adress,E.Prio1,E.Prio2,E.Prio3,E.mergeAdress,E.long,E.lat,Namn,fme_geometry{0}"
    -> Sampler
Sampler
    SAMPLE_MODE = No
    SAMPLE_TYPE_LONG = Every Nth Feature
    RATE = 1000
    SAMPLED -> FULL_JOIN [Elever]
GroupByAttribute: AttributeManager
    ATTR_TABLE = SET_TO GroupByMe = 1
    -> Aggregator
Aggregator
    GROUP_BY = GroupByMe
    SEP = ,
    MODE = Attributes Only
    ORDERED = No
    CONCAT_ATTRS = Adress Skola
    ACCUM_ATTRS_NAME = Merge Incoming Attributes
    AGGREGATE -> Terminator
Terminator
    MESSAGE = Ej mappad adress till skola @Value(Adress)
FULL_JOIN: InlineQuerier
    QUERY_SCHEMA = Output_2,S.Adress,varchar(200),S.Skola,varchar(200),S.mergeAdress,varchar(200),S.long,varchar(200),S.lat,varchar(200),Skolor.fme_feature_content,fme_feature_content,E.Adress,varchar(200),E.Prio1,varchar(200),E.Prio2,varchar(200),E.Prio3,varchar(200),E.mergeAdress,varchar(200),E.long,varchar(200),E.lat,varchar(200),Elever.fme_feature_content,fme_feature_content
    TABLE_DEF = Skolor,S.Adress,varchar(200),S.Skola,varchar(200),S.mergeAdress,varchar(200),S.long,varchar(200),S.lat,varchar(200),Elever,E.Adress,varchar(200),E.Prio1,varchar(200),E.Prio2,varchar(200),E.Prio3,varchar(200),E.mergeAdress,varchar(200),E.long,varchar(200),E.lat,varchar(200)
    QUERY_DEF = Output_2,SELECT * FROM Skolor CROSS JOIN Elever,FIRST
    Output_2 -> request
request: AttributeCreator
    ATTR_TABLE = SET_TO request = $(api_graphhopper_url)/route?point=@Value(E.lat)%2C@Value(E.long)&point=@Value(S.lat)%2C@Value(S.long)&vehicle=foot&locale=sv_SE&points_encoded=false&instructions=false&weighting=shortest&key=$(key)
    -> FeatureMerger_4 [REQUESTOR]
FeatureMerger_4
    JOIN_KEYS = @Value(request) @Value(request) AUTO
    SUPPLIERS_FIRST = No
    IGNORE_NULLS = No
    MERGE_TYPE = Attributes Only
    ATTR_CONFLICT_RES = Use Requestor
    PROCESS_DUPS = No
    ATTR_ACCUM_MODE = Merge Supplier
    REJECT_NULL_MISSING_KEYS = No
    MERGED -> JSONExtractor_2
    UNMERGED_REQUESTOR -> Graphhopper_Caller
Graphhopper_Caller: HTTPCaller
    VERIFY_SSL_CERTIFICATES = Yes
    TARGET_ATTR_ENCODING = auto-detect
    FOLLOW_REDIRECTS = Yes
    ERROR_ATTR = _error
    RESPONSE_HEADER_LIST_ATTR = _headers
    TARGET_URL = @Value(request)
    CONNECTION_TIMEOUT_LENGTH = 60
    USE_COOKIES = No
    TRANSFER_TIMEOUT_LENGTH = 90
    STATUS_CODE_ATTR = _http_status_code
    TARGET_ATTR = _response_body
    SAVE_FILE = Attribute
    HTTP_METHOD = GET
    -> JSONExtractor_2
    -> Only_new_once [SUPPLIER]
    <Rejected> -> ErrorWriter [<Rejected>]
JSONExtractor_2
    EXTRACT_QUERY_TABLE = distance json["paths"][0]["distance"] points json["paths"][0]["points"]
    JSON_DOCUMENT = @Value(_response_body)
    EVALUATED -> AttributeManager_4
    <REJECTED> -> ErrorWriter [<Rejected>00]
ErrorWriter: FeatureWriter
    DATASET = resultat\Error.xlsx
    XLSXW_PROTECT_SHEET = NO
    DATASET_ATTR = _dataset
    XLSXW_TRUNCATE_TABLE = No
    XLSXW_RASTER_FORMAT = PNG
    XLSXW_DESTINATION_DATASETTYPE_VALIDATION = Yes
    FEATURE_TYPE_LIST_ATTR = _feature_type
    XLSXW_OVERWRITE_FILE = Yes
    FORMAT = XLSXW
    XLSXW_DROP_TABLE = No
    XLSXW_FIELD_NAMES_OUT = Yes
    XLSXW_WRITER_MODE = Insert
    TOTAL_FEATURES_WRITTEN_ATTR = _total_features_written
AttributeManager_4
    ATTR_TABLE:
      REMOVE S.Adress
      REMOVE S.mergeAdress
      REMOVE S.long
      REMOVE S.lat
      RENAME_SET_VALUE E.Adress > Adress
      RENAME_SET_VALUE E.Prio1 > Prio1
      RENAME_SET_VALUE E.Prio2 > Prio2
      RENAME_SET_VALUE E.Prio3 > Prio3
      REMOVE E.mergeAdress
      REMOVE E.long
      REMOVE E.lat
      REMOVE _headers{}.name
      REMOVE _headers{}.value
      RENAME_SET_VALUE S.Skola > Skola
      REMOVE _http_status_code
      SET_TO distance = @Value(distance)
      SET_TO karta = http://geojson.io/#data=data:application/json,@Value(points)
      SET_TO points
      RENAME_SET_VALUE _response_body > response
    -> StatisticsCalculator
    -> FeatureMerger_3 [REQUESTOR]
    -> AttributeManager_4_Output
AttributeManager_4_Output: Inspector
AttributeManager_5
    ATTR_TABLE:
      RENAME_SET_VALUE _min > Kortast
      REMOVE _max
      REMOVE _median
      REMOVE _count
      REMOVE _numeric_count
      REMOVE _sum
      REMOVE _range
      REMOVE _mean
      REMOVE _stdev
      REMOVE _stdevp
      REMOVE _mode
      SET_TO RelativNarhet = @int32(@sub(@Value(distance),@Value(Kortast)))
      SET_TO distance = @int32(@Value(distance))
      REMOVE points
      REMOVE request
      REMOVE response
      REMOVE UniqValue
      REMOVE fme_geometry{0}
      REMOVE json_ogc_wkt_crs
      REMOVE json_geometry.type
      REMOVE json_geometry.coordinates{}
      REMOVE fme_geometry{}
    -> Relativ närhet (writer XLSXW_1)
Relativ närhet (writer XLSXW_1)
    attributes: Namn auto(20), Kortast auto(20), Adress auto(20), Prio1 auto(20), Prio2 auto(20), Prio3 auto(20), Skola auto(20), RelativNarhet auto(20), distance auto(20), karta auto(20)
DuplicateFilter
    KEYATTR = Namn
    INPUT_ORDERED_CHOICE = No
    UNIQUE -> InlineQuerier [Merged]
AttributeKeeper
    KEEP_ATTRS = UniqValue,Skola,distance,_min
    -> AttributeManager
AttributeManager
    ATTR_TABLE:
      RENAME_SET_VALUE Skola > s
      RENAME_SET_VALUE distance > d
      RENAME_SET_VALUE UniqValue > u
      RENAME_SET_VALUE _min > min
    -> InlineQuerier [Output]
InlineQuerier
    QUERY_SCHEMA = Merged,Namn,varchar(200),Adress,varchar(200),Prio1,varchar(200),Rel1,,Dist1,varchar(200),Prio2,varchar(200),Rel2,,Dist2,varchar(200),Prio3,varchar(200),Rel3,,Dist3,varchar(200),Skola,varchar(200),"Skola dist",varchar(200)
    TABLE_DEF = Merged,Namn,varchar(200),Adress,varchar(200),Prio1,varchar(200),Prio2,varchar(200),Prio3,varchar(200),Skola,varchar(200),distance,varchar(200),karta,varchar(200),points,varchar(200),request,varchar(200),response,varchar(200),fme_geometry{0},varchar(200),UniqValue,varchar(200),json_ogc_wkt_crs,varchar(200),json_geometry.type,varchar(200),json_geometry.coordinates{},varchar(200),_min,varchar(200),_max,varchar(200),_median,varchar(200),_count,varchar(200),_numeric_count,varchar(200),_sum,varchar(200),_range,varchar(200),_mean,varchar(200),_stdev,varchar(200),_stdevp,varchar(200),_mode,varchar(200),Output,s,varchar(200),d,varchar(200),u,varchar(200),min,varchar(200)
    QUERY_DEF:
      Merged,SELECT "Namn","Adress"
      ,"Prio1", (SELECT "d" from "Output" where "UniqValue" = "u" AND "Prio1" = "s")  - "_min" as Rel1, (SELECT "d" from "Output" where "UniqValue" = "u" AND "Prio1" = "s") as Dist1
      ,"Prio2", (SELECT "d" from "Output" where "UniqValue" = "u" AND "Prio2" = "s")  - "_min" as Rel2, (SELECT "d" from "Output" where "UniqValue" = "u" AND "Prio2" = "s") as Dist2
      ,"Prio3", (SELECT "d" from "Output" where "UniqValue" = "u" AND "Prio3" = "s")  - "_min" as Rel3, (SELECT "d" from "Output" where "UniqValue" = "u" AND "Prio3" = "s") as Dist3
      ,(SELECT "s" from "Output" where "UniqValue" = "u" AND "min" = "d")  as "Skola"
      ,(SELECT "d" from "Output" where "UniqValue" = "u" AND "min" = "d")  as "Skola dist"
      FROM "Merged" ,FIRST
    Merged -> InlineQuerier_res
InlineQuerier_res: Inspector
AttributeManager_6
    ATTR_TABLE:
      RENAME_SET_VALUE _min > Kortast
      REMOVE _max
      REMOVE _median
      REMOVE _count
      REMOVE _numeric_count
      REMOVE _sum
      REMOVE _range
      REMOVE _mean
      REMOVE _stdev
      REMOVE _stdevp
      REMOVE _mode
      REMOVE Adress
      REMOVE Prio1
      REMOVE Prio2
      REMOVE Prio3
      SET_TO RelativNarhet = @int32(@sub(@Value(distance),@Value(Kortast)))
      SET_TO distance = @int32(@Value(distance))
      REMOVE points
      REMOVE UniqValue
      REMOVE json_ogc_wkt_crs
      REMOVE json_geometry.type
      REMOVE json_geometry.coordinates{}
      REMOVE fme_geometry{}
    -> AvståndTillSkolaMeta (writer XLSXW_2)
AvståndTillSkolaMeta (writer XLSXW_2)
    attributes: Namn auto(20), Kortast auto(20), Skola auto(20), RelativNarhet auto(20), distance auto(20), karta auto(20), request auto(20), response auto(20)

Bookmark: Data från excel
Skolor_eller_elever: Tester
    BOOL_OP = OR
    TEST_DESCRIPTION = ""
    TEST_CLAUSE:
      TEST $(CachedElev) = Nej
      TEST $(CachedSkolor) = Nej
    TEST_MODE = Automatic
    PASSED -> FeatureReader_4 [INITIATOR]
    PASSED -> FeatureReader_5 [INITIATOR]
FeatureReader_4
    DATASET = $(FME_MF_DIR_ENCODED)Indata\Skolor_Sokande.xlsx
    XLSXR_FORCE_DATETIME = NO
    ATTR_ACCUM_MODE = Only Use Result
    FORMAT = XLSXR
    XLSXR_EXCEL_COL_NAMES = YES
    XLSXR_EXPAND_MERGED_CELLS = Yes
    INTERACT = <No Spatial Filter>
    XLSXR_READ_BLANK_AS = Missing
    OUTPUT_FEATURES_DISPLAY = Schema and Data Features
    COMBINE_GEOM = Use Result
    ATTRIBUTES = "Adresser skolor","Skola,Adress",Skolval,"Prio1,Prio2,Prio3,Namn,Adress,PostNr,PostOrt,Nykoid,AnnanSkolaNamn,BehallerPlatsPaFSK,ArskursAttBorjaI,Easting_Koordinat,Northing_Koordinat,SkapadAnvandare,SkapadDatum,TilldeladSkola,Q"
    XLSXR_QUERY_FEATURE_TYPES_FOR_MERGE_FILTERS = Yes
    XLSXR_SCAN_SCHEMA_IF_DYNAMIC = No
    XLSXR_USE_SCHEMA_OTHER_FILES = No
    Adresser skolor -> Tester
    Skolval -> Tester_2
Tester
    BOOL_OP = AND
    TEST_DESCRIPTION = ""
    TEST_CLAUSE:
      TEST @Value(Adress) ATTRIBUTE_HAS_VALUE ""
      TEST $(CachedSkolor) = Nej
    TEST_MODE = Automatic
    PASSED -> Städar_upp_skoladresser [AttributeCreator_2_Input]
    FAILED -> ErrorWriter [Sheet1]
Städar_upp_skoladresser: Städar upp skoladresser
    Hällestad_Output -> FeatureMerger_2 [REQUESTOR]
Tester_2
    BOOL_OP = AND
    TEST_DESCRIPTION = ""
    TEST_CLAUSE:
      TEST Adress NOT_ATTRIBUTE_VALUE_NULL ""
      TEST @Value(Adress) NOT_BEGINS_WITH NULL
      TEST $(CachedElev) = Nej
    TEST_MODE = Automatic
    PASSED -> Städa_upp_elev_adress [NullAttributeMapper_Input]
    FAILED -> ErrorWriter [Failed]
Städa_upp_elev_adress: Städa upp elev adress
    ADRESS = @Value(Adress)
    POSTNR = @Value(PostNr)
    POSTORT = @Value(PostOrt)
    AttributeKeeper_2_Output -> FeatureMerger [REQUESTOR]
FeatureReader_5
    FORMAT = GEODATABASE_SDE
    GEODATABASE_SDE_SPLIT_MULTI_PART_ANNOS = no
    ATTRIBUTES = LUND.KK_ADRESSGALLANDE,"OBJECTID,ADRESS,OMRADE,NR,NR_LIT,PUNKTLAGE,POPULARNAMN,POSTNR,POSTORT,FASTIGHET,KOMMUNDEL,E,N"
    GEODATABASE_SDE_SPLIT_COMPLEX_ANNOS = no
    INTERACT = <No Spatial Filter>
    GEODATABASE_SDE_FEATURE_READ_MODE = Features
    GEODATABASE_SDE_REMOVE_TABLE_QUALIFIER = NO
    ATTR_ACCUM_MODE = Only Use Result
    GEODATABASE_SDE_CREDENTIALS_OVERRIDE = NO
    OUTPUT_FEATURES_DISPLAY = Schema and Data Features
    GEODATABASE_SDE_IGNORE_NETWORK_INFO = yes
    COMBINE_GEOM = Use Result
    GEODATABASE_SDE_TRANSLATE_SPATIAL_DATA_ONLY = no
    GEODATABASE_SDE_QUERY_FEATURE_TYPES_FOR_MERGE_FILTERS = Yes
    GEODATABASE_SDE_CHECK_SIMPLE_GEOM = no
    GEODATABASE_SDE_MERGE_FEAT_LINKED_ANNOS = no
    GEODATABASE_SDE_SPLIT_COMPLEX_EDGES = no
    GEODATABASE_SDE_CACHE_MULTIPATCH_TEXTURES = yes
    GEODATABASE_SDE_IGNORE_RELATIONSHIP_INFO = yes
    FEATURETYPES = LUND.KK_ADRESSGALLANDE
    GEODATABASE_SDE_READ_VERSION_DIFFERENCES = NO
    GEODATABASE_SDE_ALIAS_MODE = NONE
    GEODATABASE_SDE_CLIP_TO_ENVELOPE = NO
    GEODATABASE_SDE_PERSISTENT_CONNECTION = no
    GEODATABASE_SDE_RESOLVE_SUBTYPE_NAMES = yes
    GEODATABASE_SDE_VERSION_TYPE = Version from SDE Connection
    GEODATABASE_SDE_RESOLVE_DOMAINS = no
    GEODATABASE_SDE_USE_SEARCH_ENVELOPE = NO
    GEODATABASE_SDE_CONNECTION_FILE = $(FME_MF_DIR)Indata\user@intern.sde
    LUND.KK_ADRESSGALLANDE -> Fixa_adresser [AttributeCreator_Input]
Fixa_adresser: Fixa adresser
    E = @Value(E)
    POPULARNAMN = @Value(POPULARNAMN)
    NR_LIT = @Value(NR_LIT)
    ADRESS = @Value(ADRESS)
    KOMMUNDEL = @Value(KOMMUNDEL)
    PUNKTLAGE = @Value(PUNKTLAGE)
    POSTNR = @Value(POSTNR)
    OMRADE = @Value(OMRADE)
    N = @Value(N)
    POSTORT = @Value(POSTORT)
    FASTIGHET = @Value(FASTIGHET)
    OBJECTID = @Value(OBJECTID)
    NR = @Value(NR)
    AttributeManager_Output -> FeatureMerger_2 [SUPPLIER]
    AttributeManager_Output -> FeatureMerger [SUPPLIER]
FeatureMerger_2
    JOIN_KEYS = @Value(Adress) @Value(mergeAdress) STRING
    SUPPLIERS_FIRST = No
    IGNORE_NULLS = No
    MERGE_TYPE = Attributes and Geometry
    ATTR_CONFLICT_RES = Use Requestor
    PROCESS_DUPS = No
    ATTR_ACCUM_MODE = Merge Supplier
    REJECT_NULL_MISSING_KEYS = No
    MERGED -> AttributeManager_2
    NOT_MERGED -> Ej_mappade_skolor
    NOT_MERGED -> GroupByAttribute
AttributeManager_2
    ATTR_TABLE:
      RENAME_SET_VALUE Adress > S.Adress
      RENAME_SET_VALUE Skola > S.Skola
      RENAME_SET_VALUE mergeAdress > S.mergeAdress
      RENAME_SET_VALUE long > S.long
      RENAME_SET_VALUE lat > S.lat
    -> FeatureWriter_3 [Output]
    -> FULL_JOIN [Skolor]
FeatureWriter_3
    DATASET = Indata\Skolor.geojson
    GEOJSON_STRICT_SPEC = Yes
    GEOJSON_WRITER_CHARSET = UTF-8
    DATASET_ATTR = _dataset
    GEOJSON_WRITE_BOM = No
    FEATURE_TYPE_LIST_ATTR = _feature_type
    GEOJSON_DESTINATION_DATASETTYPE_VALIDATION = Yes
    FORMAT = GEOJSON
    GEOJSON_INDENT_SIZE = 0
    GEOJSON_COUNTER_CLOCKWISE_AREAS = Yes
    GEOJSON_PRETTY_PRINT = YES
    TOTAL_FEATURES_WRITTEN_ATTR = _total_features_written
Ej_mappade_skolor: Inspector
FeatureMerger
    JOIN_KEYS = @Value(Adress) @Value(mergeAdress) STRING
    SUPPLIERS_FIRST = No
    IGNORE_NULLS = No
    MERGE_TYPE = Attributes and Geometry
    ATTR_CONFLICT_RES = Use Requestor
    PROCESS_DUPS = No
    ATTR_ACCUM_MODE = Merge Supplier
    REJECT_NULL_MISSING_KEYS = No
    MERGED -> AttributeManager_3
    NOT_MERGED -> ErrorWriter [Sheet100]
AttributeManager_3
    ATTR_TABLE:
      RENAME_SET_VALUE Adress > E.Adress
      RENAME_SET_VALUE Prio1 > E.Prio1
      RENAME_SET_VALUE Prio2 > E.Prio2
      RENAME_SET_VALUE Prio3 > E.Prio3
      RENAME_SET_VALUE mergeAdress > E.mergeAdress
      RENAME_SET_VALUE long > E.long
      RENAME_SET_VALUE lat > E.lat
    -> AttributeCreator_5
AttributeCreator_5
    ATTR_TABLE = SET_TO UniqValue = @UUID()
    -> FeatureWriter [Output]
    -> FULL_JOIN [Elever]
FeatureWriter
    DATASET = Indata\elever.geojson
    GEOJSON_STRICT_SPEC = Yes
    GEOJSON_WRITER_CHARSET = UTF-8
    DATASET_ATTR = _dataset
    GEOJSON_WRITE_BOM = No
    FEATURE_TYPE_LIST_ATTR = _feature_type
    GEOJSON_DESTINATION_DATASETTYPE_VALIDATION = Yes
    FORMAT = GEOJSON
    GEOJSON_INDENT_SIZE = 0
    GEOJSON_COUNTER_CLOCKWISE_AREAS = Yes
    GEOJSON_PRETTY_PRINT = YES
    TOTAL_FEATURES_WRITTEN_ATTR = _total_features_written

Bookmark: Metadata
Creator
    GEOMTYPE = Geometry Object
    NUM = 1
    CREATED -> Graphhopper_Caller_2
Graphhopper_Caller_2: HTTPCaller
    VERIFY_SSL_CERTIFICATES = Yes
    FOLLOW_REDIRECTS = Yes
    ERROR_ATTR = _error
    RESPONSE_HEADER_LIST_ATTR = _headers
    TARGET_URL = $(api_graphhopper_url)/info?key=$(key)
    CONNECTION_TIMEOUT_LENGTH = 60
    USE_COOKIES = No
    SAVE_MULTI = No
    FILE_PATH_ATTR = _response_file_path
    TRANSFER_TIMEOUT_LENGTH = 90
    STATUS_CODE_ATTR = _http_status_code
    OUTPUT_FILENAME = Resultat\metadata.json
    SAVE_FILE = File
    HTTP_METHOD = GET

Bookmark: Cached calls
Note: För att tömma cached calls till graphhopper ta bort alla fileri /graphopper/
Creator_2
    GEOMTYPE = Geometry Object
    NUM = 1
    CREATED -> FeatureReader [INITIATOR]
FeatureReader
    DATASET = $(FME_MF_DIR_ENCODED)graphopper\*.json
    JSON_USE_SEARCH_ENVELOPE = NO
    JSON_CLIP_TO_ENVELOPE = NO
    ATTR_ACCUM_MODE = Only Use Result
    FEATURETYPES = calls
    FORMAT = JSON
    JSON_DECODE_TEXT_STRINGS = Yes
    JSON_FLATTEN_MODE = ALL_LEVELS
    JSON_USE_BASENAME_AS_DEFAULT_FEATURE_TYPE = No
    JSON_SAVE_FRAGMENTS = NO
    JSON_FEATURE_TYPE_KEY = json_featuretype
    OUTPUT_FEATURES_DISPLAY = Schema and Data Features
    COMBINE_GEOM = Use Result
    JSON_GEOMETRY_FORMAT = None
    ATTRIBUTES = calls,"request,_response_body,_http_status_code,json_ogc_wkt_crs,json_geometry.type,json_geometry.coordinates{},fme_geometry{0}"
    JSON_SCAN_MODE = AUTO
    calls -> Only_new_once [REQUESTOR]
    calls -> FeatureMerger_4 [SUPPLIER]
Only_new_once: FeatureMerger
    JOIN_KEYS = @Value(request) @Value(request) AUTO
    SUPPLIERS_FIRST = No
    IGNORE_NULLS = No
    MERGE_TYPE = Attributes Only
    ATTR_CONFLICT_RES = Use Requestor
    PROCESS_DUPS = No
    ATTR_ACCUM_MODE = Merge Supplier
    REJECT_NULL_MISSING_KEYS = No
    UNUSED_SUPPLIER -> Cache_calls [Output]
Cache_calls: FeatureWriter
    DATASET = graphopper/$(graphhopperCacheFileName)
    JSON_WRITE_FEATURE_TYPE_KEY = YES
    JSON_COORDINATE_SYSTEM_KEY = json_ogc_wkt_crs
    JSON_GEOMETRY_KEY = json_geometry
    JSON_WRITER_CHARSET = UTF-8
    JSON_DESTINATION_DATASETTYPE_VALIDATION = Yes
    DATASET_ATTR = _dataset
    JSON_COORDINATE_SYSTEM_FORMAT = OGC-WKT
    JSON_GEOMETRY_FORMAT = GeoJSON
    FEATURE_TYPE_LIST_ATTR = _feature_type
    JSON_FEATURE_TYPE_KEY = json_featuretype
    FORMAT = JSON
    JSON_WRITE_COORDINATE_SYSTEM = YES
    JSON_WRITE_GEOMETRY = YES
    JSON_PRETTY_PRINT = YES
    JSON_WRITE_BOM = No
    JSON_INDENT_SIZE = 0
    TOTAL_FEATURES_WRITTEN_ATTR = _total_features_written

Bookmark: Relativ närhet
StatisticsCalculator
    GROUP_BY = UniqValue
    STDEVP_ATTR = _stdevp
    COMPUTE_HISTOGRAM = NO
    MODE_ATTR = _mode
    SUM_ATTR = _sum
    COUNT_ATTR = _count
    NUMERIC_ATTR = _numeric_count
    PREPEND_ATTR_NAME_CHOICE = For multiple results only
    STATS_ATTRS = distance
    MAX_ATTR = _max
    MIN_ATTR = _min
    MEDIAN_ATTR = _median
    STDEV_ATTR = _stdev
    MEAN_ATTR = _mean
    RANGE_ATTR = _range
    SUMMARY -> FeatureMerger_3 [SUPPLIER]
FeatureMerger_3
    JOIN_KEYS = @Value(UniqValue) @Value(UniqValue) AUTO
    SUPPLIERS_FIRST = No
    IGNORE_NULLS = No
    MERGE_TYPE = Attributes Only
    ATTR_CONFLICT_RES = Use Requestor
    PROCESS_DUPS = No
    ATTR_ACCUM_MODE = Merge Supplier
    REJECT_NULL_MISSING_KEYS = No
    MERGED -> DuplicateFilter
    MERGED -> AttributeManager_6
    MERGED -> AttributeManager_5
    MERGED -> AttributeKeeper

FME custom transformer Städa upp elev adress

Parameters:
- POSTNR = @Value(PostNr)   # PostNr
- ADRESS = @Value(Adress)   # Adress
- POSTORT = @Value(PostOrt)   # PostOrt

NullAttributeMapper_Input (input)
    -> NullAttributeMapper

Bookmark: Städa upp elev adress
NullAttributeMapper
    ATTRLIST = Adress
    NULL_TREATMENT = Missing
    ATTRCHOICE = Selected Attributes
    SOURCE_ATTR_VAL = Null
    -> Lgh
Lgh: StringReplacer
    REGEXP = YES
    NO_MATCH = _FME_NO_OP_
    CASE = NO
    SRC_ATTRS = Adress
    FIND_TEXT = " lgh\\s?\\d{1,4}"
    -> Läg
Läg: StringReplacer
    REGEXP = YES
    NO_MATCH = _FME_NO_OP_
    CASE = NO
    SRC_ATTRS = Adress
    FIND_TEXT = " läg\\s?\\d*"
    -> Vån
Vån: StringReplacer
    REGEXP = YES
    NO_MATCH = _FME_NO_OP_
    CASE = NO
    SRC_ATTRS = Adress
    FIND_TEXT = " VÅN\\s?\\d+"
    -> TR
TR: StringReplacer
    REGEXP = YES
    NO_MATCH = _FME_NO_OP_
    CASE = NO
    SRC_ATTRS = Adress
    FIND_TEXT = \d+\s?TR
    -> Space_2
Space_2: StringReplacer
    REGEXP = NO
    NO_MATCH = _FME_NO_OP_
    CASE = NO
    REPLACE_TEXT = " "
    SRC_ATTRS = Adress
    FIND_TEXT = " "
    -> Kommatecken
Kommatecken: StringReplacer
    REGEXP = YES
    NO_MATCH = _FME_NO_OP_
    CASE = NO
    SRC_ATTRS = Adress
    FIND_TEXT = ,.*
    -> AttributeCreator_3
AttributeCreator_3
    ATTR_TABLE = SET_TO Adress = @UpperCase(@Value(Adress), @Substring(@Value(PostNr),0,3) @Substring(@Value(PostNr),3,2) @Value(PostOrt))
    -> Hällestad_2
Hällestad_2: StringReplacer
    REGEXP = NO
    NO_MATCH = _FME_NO_OP_
    CASE = NO
    REPLACE_TEXT = TORNA-HÄLLESTAD
    SRC_ATTRS = Adress
    FIND_TEXT = TORNA HÄLLESTAD
    -> BV
BV: StringReplacer
    REGEXP = NO
    NO_MATCH = _FME_NO_OP_
    CASE = NO
    REPLACE_TEXT = ,
    SRC_ATTRS = Adress
    FIND_TEXT = " BV,"
    -> Kommatecken_2
Kommatecken_2: StringReplacer
    REGEXP = NO
    NO_MATCH = _FME_NO_OP_
    CASE = NO
    REPLACE_TEXT = ", "
    SRC_ATTRS = Adress
    FIND_TEXT = " , "
    -> AttributeKeeper_2
AttributeKeeper_2
    KEEP_ATTRS = Adress,Prio1,Prio3,Prio2,Namn
    -> AttributeKeeper_2_Output (output)
AttributeKeeper_2_Output (output)

FME custom transformer Fixa adresser

Parameters:
- PUNKTLAGE = @Value(PUNKTLAGE)
- KOMMUNDEL = @Value(KOMMUNDEL)
- N = @Value(N)
- NR = @Value(NR)
- E = @Value(E)
- POSTNR = @Value(POSTNR)
- OBJECTID = @Value(OBJECTID)
- OMRADE = @Value(OMRADE)
- POSTORT = @Value(POSTORT)
- POPULARNAMN = @Value(POPULARNAMN)
- NR_LIT = @Value(NR_LIT)   # Nr Lit
- ADRESS = @Value(ADRESS)
- FASTIGHET = @Value(FASTIGHET)

AttributeCreator_Input (input)
    -> AttributeCreator
AttributeCreator
    ATTR_TABLE = SET_TO mergeAdress = @UpperCase(@Value(OMRADE) @Trim(@Value(NR) @Value(NR_LIT)), @Value(POSTNR) @Value(POSTORT))
    -> Reprojector
Reprojector
    RASTER_CELL_SIZE = Preserve Cells
    DEST = LL-WGS84
    SOURCE = Read from feature
    INTERPOLATION_TYPE_NAME = Nearest Neighbor
    REPROJECTED -> CoordinateExtractor
CoordinateExtractor
    Z_ATTR = _z
    IND = 0
    MODE = Specify Coordinate
    Y_ATTR = _y
    X_ATTR = _x
    -> AttributeManager
AttributeManager
    ATTR_TABLE:
      RENAME_SET_VALUE _x > long
      RENAME_SET_VALUE _y > lat
      REMOVE _z
      REMOVE OBJECTID
      REMOVE ADRESS
      REMOVE OMRADE
      REMOVE NR
      REMOVE NR_LIT
      REMOVE PUNKTLAGE
      REMOVE POPULARNAMN
      REMOVE POSTNR
      REMOVE POSTORT
      REMOVE FASTIGHET
      REMOVE KOMMUNDEL
      REMOVE E
      REMOVE N
    -> AttributeManager_Output (output)
AttributeManager_Output (output)

FME custom transformer Städar upp skoladresser

AttributeCreator_2_Input (input)
    -> AttributeCreator_2

Bookmark: Städar upp skoladresser
AttributeCreator_2
    ATTR_TABLE = SET_TO Adress = @UpperCase(@Value(Adress))
    -> Space
Space: StringReplacer
    REGEXP = NO
    NO_MATCH = _FME_NO_OP_
    CASE = NO
    REPLACE_TEXT = " "
    SRC_ATTRS = Adress
    FIND_TEXT = " "
    -> Hällestad
Hällestad: StringReplacer
    REGEXP = NO
    NO_MATCH = _FME_NO_OP_
    CASE = NO
    REPLACE_TEXT = TORNA-HÄLLESTAD
    SRC_ATTRS = Adress
    FIND_TEXT = TORNA HÄLLESTAD
    -> Hällestad_Output (output)
Hällestad_Output (output)
